-- ============================================================
-- E2SM-KPM v3.0 — Key Performance Measurement Service Model
-- Subset for IoT-NTN Tracker xApp (APER encoding)
--
-- Reference: O-RAN.WG3.E2SM-KPM-v03.00
-- Only types needed for decoding RIC_INDICATION payloads
-- containing RSRP/RSRQ/SINR measurement data.
-- ============================================================

E2SM-KPM-IEs {
    iso(1) identified-organization(3) dod(6) internet(1)
    private(4) enterprise(1) oran(53148) e2(1)
    version3(3) e2sm(2) e2sm-kpm-ies(2)
}

DEFINITIONS AUTOMATIC TAGS ::=

BEGIN

-- ============================================================
-- Indication Header
-- ============================================================

E2SM-KPM-IndicationHeader ::= CHOICE {
    indicationHeader-Format1    E2SM-KPM-IndicationHeader-Format1,
    ...
}

E2SM-KPM-IndicationHeader-Format1 ::= SEQUENCE {
    colletStartTime             TimeStamp,
    fileFormatversion           PrintableString (SIZE(0..15))    OPTIONAL,
    senderName                  PrintableString (SIZE(0..400))   OPTIONAL,
    senderType                  PrintableString (SIZE(0..300))   OPTIONAL,
    vendorName                  PrintableString (SIZE(0..32))    OPTIONAL,
    ...
}

-- ============================================================
-- Indication Message
-- ============================================================

E2SM-KPM-IndicationMessage ::= CHOICE {
    indicationMessage-Format1   E2SM-KPM-IndicationMessage-Format1,
    indicationMessage-Format2   E2SM-KPM-IndicationMessage-Format2,
    indicationMessage-Format3   E2SM-KPM-IndicationMessage-Format3,
    ...
}

E2SM-KPM-IndicationMessage-Format1 ::= SEQUENCE {
    measData                    MeasurementData,
    measInfoList                MeasurementInfoList         OPTIONAL,
    granulPeriod                GranularityPeriod           OPTIONAL,
    ...
}

E2SM-KPM-IndicationMessage-Format2 ::= SEQUENCE {
    measData                    MeasurementData,
    measCondUEidList            MeasurementCondUEidList,
    granulPeriod                GranularityPeriod           OPTIONAL,
    ...
}

E2SM-KPM-IndicationMessage-Format3 ::= SEQUENCE {
    ueMeasReportList            UEMeasurementReportList,
    ...
}

-- ============================================================
-- Measurement Data Structures
-- ============================================================

MeasurementData ::= SEQUENCE (SIZE(1..65535)) OF MeasurementDataItem

MeasurementDataItem ::= SEQUENCE {
    measRecord                  MeasurementRecord,
    incompleteFlag              ENUMERATED {true, ...}      OPTIONAL,
    ...
}

MeasurementRecord ::= SEQUENCE (SIZE(1..65535)) OF MeasurementRecordItem

MeasurementRecordItem ::= CHOICE {
    integer                     INTEGER (0..4294967295),
    real                        REAL,
    noValue                     NULL,
    ...
}

-- ============================================================
-- Measurement Info
-- ============================================================

MeasurementInfoList ::= SEQUENCE (SIZE(1..65535)) OF MeasurementInfoItem

MeasurementInfoItem ::= SEQUENCE {
    measType                    MeasurementType,
    labelInfoList               LabelInfoList,
    ...
}

MeasurementType ::= CHOICE {
    measName                    MeasurementTypeName,
    measID                      MeasurementTypeID,
    ...
}

MeasurementTypeName ::= PrintableString (SIZE(1..150))
MeasurementTypeID ::= INTEGER (1..65536)

LabelInfoList ::= SEQUENCE (SIZE(1..65535)) OF LabelInfoItem

LabelInfoItem ::= SEQUENCE {
    measLabel                   MeasurementLabel,
    ...
}

MeasurementLabel ::= SEQUENCE {
    plmnID                      OCTET STRING (SIZE(3))      OPTIONAL,
    sliceID                     S-NSSAI                     OPTIONAL,
    fiveQI                      FiveQI                      OPTIONAL,
    qFI                         QosFlowIdentifier           OPTIONAL,
    qCI                         QCI                         OPTIONAL,
    qCImax                      QCI                         OPTIONAL,
    qCImin                      QCI                         OPTIONAL,
    aRPmax                      INTEGER (1..15)             OPTIONAL,
    aRPmin                      INTEGER (1..15)             OPTIONAL,
    bitrateRange                INTEGER (1..65535)          OPTIONAL,
    layerMU-MIMO                INTEGER (1..65535)          OPTIONAL,
    sUM                         ENUMERATED {true, ...}      OPTIONAL,
    distBinX                    INTEGER (1..65535)          OPTIONAL,
    distBinY                    INTEGER (1..65535)          OPTIONAL,
    distBinZ                    INTEGER (1..65535)          OPTIONAL,
    preLabelOverride            PreLabelOverride            OPTIONAL,
    startEndInd                 StartEndInd                 OPTIONAL,
    min                         ENUMERATED {true, ...}      OPTIONAL,
    max                         ENUMERATED {true, ...}      OPTIONAL,
    avg                         ENUMERATED {true, ...}      OPTIONAL,
    ...
}

PreLabelOverride ::= SEQUENCE {
    ...
}

StartEndInd ::= ENUMERATED {
    start,
    end,
    ...
}

-- ============================================================
-- UE Measurement Report List (Format 3)
-- ============================================================

UEMeasurementReportList ::= SEQUENCE (SIZE(1..65535)) OF UEMeasurementReportItem

UEMeasurementReportItem ::= SEQUENCE {
    ueID                        UEID,
    measReport                  E2SM-KPM-IndicationMessage-Format1,
    ...
}

-- ============================================================
-- Condition-based UE List (Format 2)
-- ============================================================

MeasurementCondUEidList ::= SEQUENCE (SIZE(1..65535)) OF MeasurementCondUEidItem

MeasurementCondUEidItem ::= SEQUENCE {
    measType                    MeasurementType,
    matchingCond                MatchingCondList,
    matchingUEidList            MatchingUEidList            OPTIONAL,
    ...
}

MatchingCondList ::= SEQUENCE (SIZE(1..32768)) OF MatchingCondItem

MatchingCondItem ::= CHOICE {
    measLabel                   MeasurementLabel,
    testCondInfo                TestCondInfo,
    ...
}

TestCondInfo ::= SEQUENCE {
    testType                    TestCond-Type,
    testExpr                    TestCond-Expression         OPTIONAL,
    testValue                   TestCond-Value              OPTIONAL,
    ...
}

TestCond-Type ::= CHOICE {
    gBR                         ENUMERATED {true, ...},
    aMBR                        ENUMERATED {true, ...},
    isStat                      ENUMERATED {true, ...},
    isCatM                      ENUMERATED {true, ...},
    rSRP                        ENUMERATED {true, ...},
    rSRQ                        ENUMERATED {true, ...},
    ...
}

TestCond-Expression ::= ENUMERATED {
    equal,
    greaterthan,
    lessthan,
    contains,
    present,
    ...
}

TestCond-Value ::= CHOICE {
    valueInt                    INTEGER,
    valueEnum                   INTEGER,
    valueBool                   BOOLEAN,
    valueBitS                   BIT STRING,
    valueOctS                   OCTET STRING,
    valuePrtS                   PrintableString,
    valueReal                   REAL,
    ...
}

MatchingUEidList ::= SEQUENCE (SIZE(1..65535)) OF MatchingUEidItem

MatchingUEidItem ::= SEQUENCE {
    ueID                        UEID,
    ...
}

-- ============================================================
-- Common Types
-- ============================================================

TimeStamp ::= OCTET STRING (SIZE(4))

GranularityPeriod ::= INTEGER (1..4294967295)

S-NSSAI ::= SEQUENCE {
    sST                         OCTET STRING (SIZE(1)),
    sD                          OCTET STRING (SIZE(3))      OPTIONAL,
    ...
}

FiveQI ::= INTEGER (0..255)
QosFlowIdentifier ::= INTEGER (0..63)
QCI ::= INTEGER (0..255)

UEID ::= CHOICE {
    gNB-UEID                    UEID-GNB,
    gNB-DU-UEID                 UEID-GNB-DU,
    gNB-CU-UP-UEID              UEID-GNB-CU-UP,
    ng-eNB-UEID                 UEID-NG-ENB,
    ng-eNB-DU-UEID              UEID-NG-ENB-DU,
    en-gNB-UEID                 UEID-EN-GNB,
    eNB-UEID                    UEID-ENB,
    ...
}

UEID-GNB ::= SEQUENCE {
    amf-UE-NGAP-ID              INTEGER (0..1099511627775),
    guami                       GUAMI,
    gNB-CU-UE-F1AP-ID-List      UEID-GNB-CU-F1AP-ID-List   OPTIONAL,
    gNB-CU-CP-UE-E1AP-ID-List   UEID-GNB-CU-CP-E1AP-ID-List OPTIONAL,
    ran-UEID                    OCTET STRING (SIZE(8))      OPTIONAL,
    m-NG-RAN-UE-XnAP-ID        INTEGER (0..4294967295)     OPTIONAL,
    globalGNB-ID                GlobalGNB-ID                OPTIONAL,
    ...
}

UEID-GNB-DU ::= SEQUENCE {
    gNB-CU-UE-F1AP-ID          INTEGER (0..4294967295),
    ran-UEID                    OCTET STRING (SIZE(8))      OPTIONAL,
    ...
}

UEID-GNB-CU-UP ::= SEQUENCE {
    gNB-CU-CP-UE-E1AP-ID       INTEGER (0..4294967295),
    ran-UEID                    OCTET STRING (SIZE(8))      OPTIONAL,
    ...
}

UEID-NG-ENB ::= SEQUENCE {
    amf-UE-NGAP-ID              INTEGER (0..1099511627775),
    guami                       GUAMI,
    ng-eNB-CU-UE-W1AP-ID       INTEGER (0..4294967295)     OPTIONAL,
    m-NG-RAN-UE-XnAP-ID        INTEGER (0..4294967295)     OPTIONAL,
    globalNgENB-ID              GlobalNgENB-ID              OPTIONAL,
    ...
}

UEID-NG-ENB-DU ::= SEQUENCE {
    ng-eNB-CU-UE-W1AP-ID       INTEGER (0..4294967295),
    ...
}

UEID-EN-GNB ::= SEQUENCE {
    m-eNB-UE-X2AP-ID           INTEGER (0..4095),
    m-eNB-UE-X2AP-ID-Extension INTEGER (0..4095)           OPTIONAL,
    globalENB-ID                GlobalENB-ID                OPTIONAL,
    ...
}

UEID-ENB ::= SEQUENCE {
    mME-UE-S1AP-ID             INTEGER (0..4294967295),
    gUMMEI                      GUMMEI,
    m-eNB-UE-X2AP-ID           INTEGER (0..4095)           OPTIONAL,
    m-eNB-UE-X2AP-ID-Extension INTEGER (0..4095)           OPTIONAL,
    globalENB-ID                GlobalENB-ID                OPTIONAL,
    ...
}

UEID-GNB-CU-F1AP-ID-List ::= SEQUENCE (SIZE(1..4)) OF UEID-GNB-CU-CP-F1AP-ID-Item

UEID-GNB-CU-CP-F1AP-ID-Item ::= SEQUENCE {
    gNB-CU-UE-F1AP-ID          INTEGER (0..4294967295),
    ...
}

UEID-GNB-CU-CP-E1AP-ID-List ::= SEQUENCE (SIZE(1..65535)) OF UEID-GNB-CU-CP-E1AP-ID-Item

UEID-GNB-CU-CP-E1AP-ID-Item ::= SEQUENCE {
    gNB-CU-CP-UE-E1AP-ID       INTEGER (0..4294967295),
    ...
}

-- ============================================================
-- Global IDs
-- ============================================================

GUAMI ::= SEQUENCE {
    pLMNIdentity                OCTET STRING (SIZE(3)),
    aMFRegionID                 BIT STRING (SIZE(8)),
    aMFSetID                    BIT STRING (SIZE(10)),
    aMFPointer                  BIT STRING (SIZE(6)),
    ...
}

GUMMEI ::= SEQUENCE {
    pLMN-Identity               OCTET STRING (SIZE(3)),
    mME-Group-ID                OCTET STRING (SIZE(2)),
    mME-Code                    OCTET STRING (SIZE(1)),
    ...
}

GlobalGNB-ID ::= SEQUENCE {
    pLMNIdentity                OCTET STRING (SIZE(3)),
    gNB-ID                      GNB-ID,
    ...
}

GNB-ID ::= CHOICE {
    gNB-ID                      BIT STRING (SIZE(22..32)),
    ...
}

GlobalNgENB-ID ::= SEQUENCE {
    pLMNIdentity                OCTET STRING (SIZE(3)),
    ngENB-ID                    NgENB-ID,
    ...
}

NgENB-ID ::= CHOICE {
    macroNgENB-ID               BIT STRING (SIZE(20)),
    shortMacroNgENB-ID          BIT STRING (SIZE(18)),
    longMacroNgENB-ID           BIT STRING (SIZE(21)),
    ...
}

GlobalENB-ID ::= SEQUENCE {
    pLMNIdentity                OCTET STRING (SIZE(3)),
    eNB-ID                      ENB-ID,
    ...
}

ENB-ID ::= CHOICE {
    macro-eNB-ID                BIT STRING (SIZE(20)),
    home-eNB-ID                 BIT STRING (SIZE(28)),
    short-Macro-eNB-ID          BIT STRING (SIZE(18)),
    long-Macro-eNB-ID           BIT STRING (SIZE(21)),
    ...
}

END
